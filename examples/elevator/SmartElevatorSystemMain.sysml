package SmartElevatorSystemMain {
    // Top-Level Package Hierarchy Imports
    public import ElevatorRequirements::*;
    public import ElevatorStructure::*;
    public import ElevatorBehavior::*;
    public import ElevatorParametrics::*;
    public import ElevatorAllocations::*;
    public import ElevatorArchitecture::*;
    public import ElevatorVerification::*;
    public import ElevatorTraceability::*;

    // Final Integrated System Instance
    part smartElevatorSystem : SmartElevatorSystem;
}
